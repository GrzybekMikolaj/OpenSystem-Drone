# dron

## #1: System shall have capability of of local data logging (Functional)
Local means logs shall be saved on internal memory

## #2: System shall provide a power managment capabilities (Functional)
Power Mangment system shall make sure that:
- Battery will not be allowed to reach unsafe state (OVC, OVT, running out of power when in air etc.)
- System will be informed of all possible battery status parameters
- System (excluding actuators) will be operational during charging with off board charger.

## #3: System shall provide multiple power modes (Functional)
System shall implement multiple power modes:
- Power Off - Battery completly shut off from any of system components
- Safe Standby - When System is in Safe Standby Mode actuators cannot be powered. Rest of the System shall be capable of diagnostic, reprograming and rest of the supported functionalities.
- Normal Operating Mode - In Normal Operating Mode System shall be fully functional.
- Maybe Fuel Gauge IC
